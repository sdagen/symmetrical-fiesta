# SystemRequirements

## SR-GS-001: Recipe count (Functional)
System shall cook at least 8 distinct recipes selectable at runtime.
- Rationale: Eight recipes gives menu variety while staying within ingredient storage and recipe-validation budgets.

## SR-GS-002: Throughput (Functional)
System shall sustain total throughput of at least 200 bowls/hour.
- Rationale: 200 bowls/hour matches expected peak order rate aggregated across customer worlds.

## SR-GS-003: Automation level (Functional)
System shall achieve average automation level of at least 0.8 across components.
- Rationale: 0.8 automation lets the 5-operator crew cover a 24/7 facility with rotation and breaks.

## SR-GS-004: Operator count (Functional)
System shall require at most 5 concurrent operators at peak load.
- Rationale: Facility berthing and life support are sized for a 5-person crew.

## SR-GS-005: Shipping manifest (Functional)
System shall generate a shipping manifest per batch including destination.
- Rationale: Manifest is required for customs, transport routing, and recipient confirmation on delivery.

## SR-GS-006: Transport loading time (Functional)
System shall load packaged soup onto transport within 10 minutes of packaging.
- Rationale: 10-minute window keeps loading pipeline aligned with the 200 bowls/hour production rate.

## SR-GS-007: Contamination detection (Functional)
System shall detect contamination before sealing with at least 99% sensitivity.
- Rationale: 99% sensitivity balances false-positive rework cost against the downstream cost of a contaminated shipment.

## SR-GS-008: Serving temperature (Functional)
System shall verify soup temperature in 70-95 C before QC sign-off.
- Rationale: 70-95 C is the safe serving range: above pathogen-kill threshold and below scald risk.

## SR-GS-009: Container seal life (Functional)
System shall seal containers rated for 30-day interstellar transit.
- Rationale: 30 days covers typical transit time to the farthest customer worlds with margin.

## SR-GS-010: Inventory accuracy (Functional)
System shall track ingredient inventory with at most 1% stock error.
- Rationale: 1% stock error keeps reorder decisions accurate enough to avoid production-halting stock-outs.

## SR-GS-011: Mass budget (Functional)
Total system mass shall not exceed 15000 kg. Stored consumables (ingredients and packaged product) are excluded from this budget (requirements decision 2026-07-08, ADR-032: resolves the SR-GS-021 storage-endurance conflict).
- Rationale: Allocated from the facility deployment mass budget.

## SR-GS-012: Power budget (Functional)
Total system power draw shall not exceed 500 kW.
- Rationale: Allocated from the facility power budget.

## SR-GS-013: Cost budget (Functional)
Total system cost shall not exceed 2000000 credits.
- Rationale: Allocated from the facility capital cost budget.

## SR-GS-014: Volume budget (Functional)
Total system volume shall not exceed 400 m^3.
- Rationale: Allocated from the facility floor-space and volume budget.

## SR-GS-015: Gravity operating range (Functional)
System shall perform all cooking, packaging, and shipping functions nominally across ambient gravity 0.1 g to 12 g.
- Rationale: 0.1-12 g spans the full ambient gravity range across candidate customer worlds.

## SR-GS-016: Structural 12 g tolerance (Functional)
System structure and mounts shall withstand sustained 12 g loading without permanent deformation.
- Rationale: 12 g is the worst-case sustained ambient gravity among customer worlds.

## SR-GS-017: Concurrent rocket support (Functional)
System shall support simultaneous handling of at least 3 delivery rockets for loading or unloading.
- Rationale: Parallel handling prevents outbound shipping from blocking inbound ingredient deliveries.

## SR-GS-018: Rocket turnaround (Functional)
System shall complete loading or unloading of a delivery rocket within 20 minutes.
- Rationale: Fast turnaround maximizes fleet utilization and maintains alignment with production throughput.

## SR-GS-019: Rocket refueling (Functional)
System shall provide on-site refueling capability for supported delivery rockets.
- Rationale: On-site refueling minimizes logistics dependencies and enables rapid redeployment.

## SR-GS-020: Temperature-controlled storage (Functional)
System shall provide separate storage zones for cold and room-temperature ingredients.
- Rationale: Different ingredient classes require different storage conditions to maintain safety and quality.

## SR-GS-021: Ingredient storage capacity (Functional)
System shall store at least 72 hours of ingredients at nominal production rate.
- Rationale: 72 hours of buffer mitigates delivery delays without exceeding storage mass and volume budgets.

## SR-GS-022: Cooking capacity (Functional)
System shall cook soup at a sustained rate sufficient to meet overall throughput requirements.
- Rationale: Cooking must not be the bottleneck in achieving 200 bowls/hour system throughput.

## SR-GS-023: Internal transfer time (Functional)
System shall transport ingredients from storage to cooking at a rate sufficient to sustain nominal cooking throughput.
- Rationale: Cooking throughput must not be limited by internal ingredient transport.

## SR-GS-024: Internal transport automation (Functional)
Internal material transport shall be automated for at least 90% of transfers.
- Rationale: High automation supports low crew size and reduces operator workload.

## SR-GS-025: Startup readiness (Functional)
System shall reach nominal operating throughput within a defined startup period after activation.
- Rationale: Ensures the system can transition from inactive to productive operation without extended downtime.

## SR-GS-026: Fault-induced throughput degredation (Functional)
System shall prevent uncontrolled termination of production due to single internal component faults.
- Rationale: Should tolerate individual component failures without complete loss of production.

## SR-GS-027: Production coordination (Functional)
System shall coordinate internal operations to satisfy throughput, safety, and logistical constraints concurrently.
- Rationale: Ensures that throughput, safety, and logistics objectives are met simultaneously in a highly automated system.

## SR-GS-028: Preparation zone (Functional)
System shall include a separate ingredient preparation zone supporting chopping and weighing of ingredients, physically isolated from storage and cooking zones. The zone shall sustain prep throughput of at least 200 bowls/hour equivalent.
- Rationale: A dedicated prep zone keeps raw/prepped materials separated and sized so it does not bottleneck the cooking line.
